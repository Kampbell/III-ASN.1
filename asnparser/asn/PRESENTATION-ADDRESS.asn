PRESENTATION-ADDRESS DEFINITIONS ::=

BEGIN

presentationAddress ATTRIBUTE ::= {
	WITH SYNTAX PresentationAddress
	EQUALITY MATCHING RULE presentationAddressMatch
	SINGLE VALUE TRUE
	ID id-at-presentationAddress
}

-- PSAPaddr ::= 
PresentationAddress ::= SEQUENCE {
	pSelector [0] OCTET STRING OPTIONAL,
	sSelector [1] OCTET STRING OPTIONAL,
	tSelector [2] OCTET STRING OPTIONAL,
	nAddresses [3] SET SIZE (1..MAX) OF OCTET STRING
}

END
