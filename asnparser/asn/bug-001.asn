BUG-001 DEFINITIONS ::=
BEGIN

OPERATION ::= CLASS {
  &id                   OBJECT IDENTIFIER UNIQUE OPTIONAL
}
WITH SYNTAX {
  [ID &id]
}

CONTRACT ::= CLASS {
  &id                   OBJECT IDENTIFIER UNIQUE OPTIONAL
}
WITH SYNTAX {
  [FOO &id]
}

-- pippo INTEGER ::= 4

-- 

rTSE-abstract-syntax OBJECT IDENTIFIER ::=  {joint-iso-itu-t(2) reliable-transfer(3) abstract-syntax(2)}

-- rTSE CONTRACT ::= {  FOO  {joint-iso-itu-t(2) foo(3)} }

-- bar CONTRACT ::= {    FOO  rTSE.&id }

-- foo CONTRACT ::= {    FOO  rTSE-abstract-syntax }

-- combine{CONTRACT:base} OPERATION ::= { ID base.&id }


END
