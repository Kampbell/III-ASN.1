-- OK: Everything is fine

-- iso.org.dod.internet.private.enterprise (1.3.6.1.4.1)
-- .spelio.software.asn1c.test (9363.1.5.1)
-- .25

ModuleTestMisc
	{ iso org(3) dod(6) internet(1) private(4) enterprise(1)
		spelio(9363) software(1) asn1c(5) test(1) 25 }
	DEFINITIONS IMPLICIT TAGS ::=
BEGIN

	Alphe ::= INTEGER {one(1), two(2) }

	T ::= SEQUENCE {
		a	INTEGER,
		b [2]	BOOLEAN,
		c	NULL,
		...,
		d	ENUMERATED {
				a(1), b(2)
				},
		e	OCTET STRING,
		f [5]	VisibleString,
		g	BIT STRING,
		h [7]	BIT STRING,
		...
	}

END
